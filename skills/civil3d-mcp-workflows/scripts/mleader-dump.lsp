;; Dumps every model-space MULTILEADER / MTEXT (layer TextTopoLabel_ep) / DIMENSION with the geometry the
;; plugin needs to replay it exactly: MLeader text, text location (context 12), text width (43), attachment
;; (171), landing (LEADER 10), dogleg (LEADER 11), arrow vertices (LEADER_LINE 10); MTEXT position, width,
;; background mask (90/45); DIMENSION points, style and DSTYLE overrides.
;; Core Console:  (setq *dumpfile* "C:/path/out.txt") (load "mleader-dump.lsp")
(defun _pt (p) (strcat (rtos (car p) 2 4) "," (rtos (cadr p) 2 4)))
(defun _esc (s) (vl-string-translate "|" "/" s))
(setq _f (open *dumpfile* "w"))
(setq _ss (ssget "X" '((0 . "MULTILEADER") (410 . "Model"))) _i 0)
(if _ss (repeat (sslength _ss)
  (setq _e (ssname _ss _i) _d (entget _e) _i (1+ _i) _out "" _txt "" _inl nil _inline nil _vtx "")
  (foreach _p _d
    (cond
      ((= (car _p) 302) (setq _inl T))
      ((and (= (car _p) 304) _inl) (setq _inline T))
      ((and (= (car _p) 304) (not _inl)) (setq _txt (cdr _p)))
      ((and (= (car _p) 12) (not _inl)) (setq _out (strcat _out "|txtloc=" (_pt (cdr _p)))))
      ((and (= (car _p) 43) (not _inl) (not (wcmatch _out "*|w=*"))) (setq _out (strcat _out "|w=" (rtos (cdr _p) 2 4))))
      ((and (= (car _p) 41) (not _inl) (not (wcmatch _out "*|h=*"))) (setq _out (strcat _out "|h=" (rtos (cdr _p) 2 4))))
      ((and (= (car _p) 171) (not _inl) (not (wcmatch _out "*|att=*"))) (setq _out (strcat _out "|att=" (itoa (cdr _p)))))
      ((and (= (car _p) 10) _inl (not _inline)) (setq _out (strcat _out "|landing=" (_pt (cdr _p)))))
      ((and (= (car _p) 11) _inl (not _inline)) (setq _out (strcat _out "|dogleg=" (_pt (cdr _p)))))
      ((and (= (car _p) 10) _inline) (setq _vtx (strcat _vtx (_pt (cdr _p)) ";")))
      ((= (car _p) 305) (setq _inline nil))
      ((= (car _p) 303) (setq _inl nil))))
  (write-line (strcat "ML|" (cdr (assoc 5 _d)) "|layer=" (cdr (assoc 8 _d)) _out "|vtx=" _vtx "|txt=" (_esc _txt)) _f)))
(setq _ss (ssget "X" '((0 . "MTEXT") (8 . "TextTopoLabel_ep") (410 . "Model"))) _i 0)
(if _ss (repeat (sslength _ss)
  (setq _d (entget (ssname _ss _i)) _i (1+ _i))
  (write-line (strcat "MT|" (cdr (assoc 5 _d)) "|x=" (_pt (cdr (assoc 10 _d))) "|w=" (rtos (cdr (assoc 41 _d)) 2 4)
    "|h=" (rtos (cdr (assoc 40 _d)) 2 4) "|rot=" (rtos (cdr (assoc 50 _d)) 2 5) "|bg=" (itoa (if (assoc 90 _d) (cdr (assoc 90 _d)) 0))
    "|bgs=" (if (assoc 45 _d) (rtos (cdr (assoc 45 _d)) 2 2) "0") "|txt=" (_esc (cdr (assoc 1 _d)))) _f)))
(setq _ss (ssget "X" '((0 . "DIMENSION") (410 . "Model"))) _i 0)
(if _ss (repeat (sslength _ss)
  (setq _e (ssname _ss _i) _d (entget _e '("ACAD" "AcadAnnotative")) _i (1+ _i))
  (write-line (strcat "DIM|" (cdr (assoc 5 _d)) "|layer=" (cdr (assoc 8 _d)) "|style=" (cdr (assoc 3 _d))
    "|p13=" (_pt (cdr (assoc 13 _d))) "|p14=" (_pt (cdr (assoc 14 _d))) "|p10=" (_pt (cdr (assoc 10 _d)))
    "|meas=" (rtos (cdr (assoc 42 _d)) 2 4) "|txt=" (_esc (cdr (assoc 1 _d)))
    "|ann=" (if (assoc "AcadAnnotative" (cdr (assoc -3 _d))) "1" "0")
    "|xd=" (vl-prin1-to-string (cdr (assoc "ACAD" (cdr (assoc -3 _d)))))) _f)))
(close _f)
(princ)
